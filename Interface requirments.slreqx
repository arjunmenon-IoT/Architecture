# Interface requirments

## Connector - PNP Sensor: M12 -> PNP Input (Functional)
| 5 pin(s)1 male connector M12 |
| --- |
Maximum Length for PNP : 10 meters (30 feet)
From <https://tesensors.com/global/en/product/reference/XGCS491B201>
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Male Pin
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
## Connector - CANJ Sensor: Deutsch 6 pin -> CANJ Input (Functional)
Deutsch 6-pin connector for this product with only 5 pins: 24V, 0V, Shield, CAN+, CAN- One pin is not used
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
## Connector - Ethernet TCP/IP: Direct to network Connector (Functional)
4 pin(s)female Ethernet socket 1 M12
4 pin(s)female Ethernet socket 2 M12
4 pin(s)male power supply socket M8
From <https://tesensors.com/global/en/product/reference/XGCS850C201>
|  | 4 pin(s)female Ethernet socket 1 M12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 |  | 4 pin(s)male power supply socket M8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 |
| --- | --- | --- | --- |
|  |  |  | 4 pin(s)male power supply socket M8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 |

## Connector - RTU to Box: RTU -> Splitter Box (Functional)
5 pin(s)male remote connector M12, shielded cable cable 0.2 m
From <https://tesensors.com/global/en/product/reference/XGCS4901201>
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
## Connector -IO Link Master: Sensor -> Io Link Master (Functional)
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The IO-Link device is coupled with the master using a standard sensor/actuator cable measuring up to 20 m in length.
From <https://www.sick.com/us/en/io-link-principles-and-technology/w/io-link-basics-and-technology/>

## Spliterbox - network: Ethernet module -> PLC (Functional)
Splitter Box (Modbus/Ethernet/Profinet)
Sources Link: SuperisysIACM-P4_________-en.pdf
RFID Port Male connector
| Extension 5-pin M12 male A, M12 female, cable length 50M |
| --- |
| XGSZ84ETH? | XGSZ84EIP? | XGSZ84PNT? |
| --- | --- | --- |
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RFID Port Male connector
Connection cable Ethernet connection
| Extension 4-pin M12 male A, M12 female, cable length 100M |
| --- |
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- Rationale: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
