# temp

# Specification: Interface requirments

## Connector - PNP Sensor: M12 -> PNP Input (Requirement)

## Connector - CANJ Sensor: Deutsch 6 pin -> CANJ Input (Requirement)
Deutsch 6-pin connector for this product with only 5 pins: 24V, 0V, Shield, CAN+, CAN- One pin is not used
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
## Connector - Ethernet TCP/IP: Direct to network Connector (Requirement)

## Connector - RTU to Box: RTU -> Splitter Box (Requirement)
s

## Connector -IO Link Master: Sensor -> Io Link Master (Requirement)
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The IO-Link device is coupled with the master using a standard sensor/actuator cable measuring up to 20 m in length.
From <https://www.sick.com/us/en/io-link-principles-and-technology/w/io-link-basics-and-technology/>

## Spliterbox - network: Ethernet module -> PLC (Requirement)
Splitter Box (Modbus/Ethernet/Profinet)
Sources Link: SuperisysIACM-P4_________-en.pdf
RFID Port Male connector
| Extension 5-pin M12 male A, M12 female, cable length 50M |
| --- |
| XGSZ84ETH? | XGSZ84EIP? | XGSZ84PNT? |
| --- | --- | --- |
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RFID Port Male connector
Connection cable Ethernet connection
| Extension 4-pin M12 male A, M12 female, cable length 100M |
| --- |
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
# Specification: Blupanda
- name: Blupanda

## :366: 5 pin-1 male connector M12 (Simulink Object)
Simulink: 5 pin-1 male connector M12
- Implement -> Connector - PNP Sensor

## :372: Deutsch 6-pin Connector (Simulink Object)
Simulink: Deutsch 6-pin Connector
- Implement -> Connector - CANJ Sensor

## :497: M12 to Ethernet 0 (Simulink Object)
Simulink: M12 to Ethernet 0
- Implement -> Connector - Ethernet TCP/IP

## :501: M12 to Ethernet 1 (Simulink Object)
Simulink: M12 to Ethernet 1
- Implement -> Connector - Ethernet TCP/IP

## :505: M12 to Ethernet 2 (Simulink Object)
Simulink: M12 to Ethernet 2
- Implement -> Connector - Ethernet TCP/IP

## :436: 5 pin Male M12 Connector (Simulink Object)
Simulink: 5 pin Male M12 Connector
- Implement -> Connector - RTU to Box

## :459: 5 pin Male M12 Connector1 (Simulink Object)
Simulink: 5 pin Male M12 Connector1
- Implement -> Connector - RTU to Box

## :478: 5 pin Male M12 Connector2 (Simulink Object)
Simulink: 5 pin Male M12 Connector2
- Implement -> Connector - RTU to Box

## :377: IO Link Cables (Simulink Object)
Simulink: IO Link Cables
- Implement -> Connector -IO Link Master

## :418: IO Link Cables_1 (Simulink Object)
Simulink: IO Link Cables_1
- Implement -> Connector -IO Link Master

## :524: Interface_box_network_1 (Simulink Object)
Simulink: Interface_box_network_1
- Implement -> Spliterbox - network

## :528: Interface_box_network_2 (Simulink Object)
Simulink: Interface_box_network_2
- Implement -> Spliterbox - network

## :532: Interface_box_network_3 (Simulink Object)
Simulink: Interface_box_network_3
- Implement -> Spliterbox - network
