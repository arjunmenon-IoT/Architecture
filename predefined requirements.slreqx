# predefined requirements
All the Requirements allocated with the RFID Components are defined in this set

## Readers: TE Mecanique Readers and Caputered requirments (Container)
Reader requirements including:
1 - Functional Requirments
2 - Enviormental Requirments
3 - Performance Requirments
4 - Interface Requirments
5 - Constraints requirements
6 - Enviormental Requirments
- Rationale: we follow the tree approach to capture all the component and its requirements

### Functional Requirments: Precise activities, capacities, or functions of system (Informational)
Functional requirements are the fundamental specifications that describe what a system is supposed to do. They define the behaviour of a system, i.e., the specific services that the system should provide to its users

### Enviormental Requirments: Physical, social, or regulatory factors that the system must comply (Functional)
environmental requirements refer to the conditions under which a system must operate

### Performance Requirments: criteria and expectations for a system to meet for performance, efficiency, and effectiveness (Functional)

### Interface Requirments: System interaction and communication with external entities (Functional)

#### XGCS491B201 - PNP: 5 pin-1 male connector M12 (Functional)
https://download.schneider-electric.com/files?p_Doc_Ref=NVE88496_EN
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Connector end :
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PIN Describtion:
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- Rationale: One Side M12
  Other side Wired for PNP

#### XGCS460B201 - CANJ: Deutsch 6-pin Connector (Functional)
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
#### Modbus_RTU_IO_Master: M12 -A coded 5 pin (Functional)
Connection to IO Master Link (female):
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Pin Config:
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Sensor end Connection:
Male 5-pin M12 connector, A-coded
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
### Enviormental Requirments: Conditions and considerations for it to function and perform properly (Functional)
